Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True

'生成巷道
Private Sub kk()

'a1 = Val(TextBox1.Text) 'jingkuang
'a2 = Val(TextBox2.Text) 'bigao
'a3 = Val(TextBox3.Text) 'bihou

'k = a1 / 2
'g = a2
'h = a3

k = 3000
g = 2000
h = 200
d = 2


'与中线偏移
z = k - 300 - 1250 - 150

If d = 1 Then
'顶圆1，2
Dim yuan1 As AcadArc


Dim yuan1xin(0 To 2) As Double
Dim yuan1banjing As Double
Dim yuan1qsjd  As Double
Dim yuan1zzjd As Double
yuan1xin(0) = 0: yuan1xin(1) = g: yuan1xin(2) = 0
yuan1banjing = k
yuan1qsjd = 0
yuan1zzjd = 3.15

Set yuan1 = ThisDrawing.ModelSpace.AddArc(yuan1xin, yuan1banjing, yuan1qsjd, yuan1zzjd)

Dim yuan2 As AcadArc
Dim yuan2xin(0 To 2) As Double
Dim yuan2banjing As Double
Dim yuan2qsjd  As Double
Dim yuan2zzjd As Double
yuan2xin(0) = 0: yuan2xin(1) = g: yuan2xin(2) = 0
yuan2banjing = k + h
yuan2qsjd = 0
yuan2zzjd = 3.15

Set yuan2 = ThisDrawing.ModelSpace.AddArc(yuan2xin, yuan2banjing, yuan2qsjd, yuan2zzjd)





ElseIf d = 2 Then


'三心拱

Dim syuanhu1 As AcadArc
Dim syuanhu1xin(0 To 2) As Double
Dim syuanhu1banjing As Double
Dim syuanhu1qsjd  As Double
Dim syuanhu1zzjd As Double
syuanhu1xin(0) = 0: syuanhu1xin(1) = g - k / 1.732: syuanhu1xin(2) = 0
syuanhu1banjing = k / 1.732 * 2
syuanhu1qsjd = 0.52
syuanhu1zzjd = 2.62
Set syuanhu1 = ThisDrawing.ModelSpace.AddArc(syuanhu1xin, syuanhu1banjing, syuanhu1qsjd, syuanhu1zzjd)

Dim syuanhu2 As AcadArc
Dim syuanhu2xin(0 To 2) As Double
Dim syuanhu2banjing As Double
Dim syuanhu2qsjd  As Double
Dim syuanhu2zzjd As Double
syuanhu2xin(0) = 0: syuanhu2xin(1) = g - k / 1.732: syuanhu2xin(2) = 0
syuanhu2banjing = k / 1.732 * 2 + 180
syuanhu2qsjd = 0.48
syuanhu2zzjd = 2.66
Set syuanhu2 = ThisDrawing.ModelSpace.AddArc(syuanhu2xin, syuanhu2banjing, syuanhu2qsjd, syuanhu2zzjd)


Else: d = 3


'圆弧

Dim yuanhu1 As AcadArc
Dim yuanhu1xin(0 To 2) As Double
Dim yuanhu1banjing As Double
Dim yuanhu1qsjd  As Double
Dim yuanhu1zzjd As Double
yuanhu1xin(0) = 0: yuanhu1xin(1) = g - k / 1.732: yuanhu1xin(2) = 0
yuanhu1banjing = k / 1.732 * 2
yuanhu1qsjd = 0.52
yuanhu1zzjd = 2.62
Set yuanhu1 = ThisDrawing.ModelSpace.AddArc(yuanhu1xin, yuanhu1banjing, yuanhu1qsjd, yuanhu1zzjd)

Dim yuanhu2 As AcadArc
Dim yuanhu2xin(0 To 2) As Double
Dim yuanhu2banjing As Double
Dim yuanhu2qsjd  As Double
Dim yuanhu2zzjd As Double
yuanhu2xin(0) = 0: yuanhu2xin(1) = g - k / 1.732: yuanhu2xin(2) = 0
yuanhu2banjing = k / 1.732 * 2 + 180
yuanhu2qsjd = 0.48
yuanhu2zzjd = 2.66
Set yuanhu2 = ThisDrawing.ModelSpace.AddArc(yuanhu2xin, yuanhu2banjing, yuanhu2qsjd, yuanhu2zzjd)

End If

'youqiang
Dim youqiang As AcadLWPolyline
Dim yqpoints(0 To 7) As Double
yqpoints(0) = k: yqpoints(1) = g
yqpoints(2) = k: yqpoints(3) = -400
yqpoints(4) = k + h: yqpoints(5) = -400
yqpoints(6) = k + h: yqpoints(7) = g

Set youqiang = ThisDrawing.ModelSpace.AddLightWeightPolyline(yqpoints)


'zuoqiang
Dim zuoqiang As AcadLWPolyline
Dim zqpoints(0 To 7) As Double
zqpoints(0) = -k: zqpoints(1) = g
zqpoints(2) = -k: zqpoints(3) = -300
zqpoints(4) = -k - h: zqpoints(5) = -300
zqpoints(6) = -k - h: zqpoints(7) = g

Set zuoqiang = ThisDrawing.ModelSpace.AddLightWeightPolyline(zqpoints)


'di
Dim di As AcadLWPolyline
Dim dpoints(0 To 3) As Double
dpoints(0) = -k: dpoints(1) = 0
dpoints(2) = k: dpoints(3) = 0

Set di = ThisDrawing.ModelSpace.AddLightWeightPolyline(dpoints)

'shuigou
x = 50 'shiuigoubihou

Dim dhuigou As AcadLWPolyline
Dim sgpoints(0 To 13) As Double
sgpoints(0) = k - x: sgpoints(1) = 0
sgpoints(2) = k - x: sgpoints(3) = -350
sgpoints(4) = k - x - 300: sgpoints(5) = -350
sgpoints(6) = k - x - 300: sgpoints(7) = 0
sgpoints(8) = k - x - 300 - x: sgpoints(9) = 0
sgpoints(10) = k - x - 300 - x: sgpoints(11) = -350 - x
sgpoints(12) = k: sgpoints(13) = -350 - x

Set shuigou = ThisDrawing.ModelSpace.AddLightWeightPolyline(sgpoints)


 
Dim zhongline As AcadLWPolyline
Dim zlpoints(0 To 3) As Double

zlpoints(0) = k: zlpoints(1) = g

zlpoints(2) = -k: zlpoints(3) = g

Set zhongline = ThisDrawing.ModelSpace.AddLightWeightPolyline(zlpoints)


'  矿车
'kuangcheqiangbu
kcqb = 300
'kuangchezhijianjianju
kcjj = 300

'kuangchekuangdu
kckd = 1250
'kuangchegaodu
kcgd = 1300
'tieguigaodu
tggd = 300

'矿车

Dim kuangche  As AcadLWPolyline
Dim kcpoints(0 To 7) As Double
kcpoints(0) = -k + kcqb: kcpoints(1) = tggd + kcgd - 150
kcpoints(2) = -k + kcqb: kcpoints(3) = tggd + kcgd
kcpoints(4) = -k + kcqb + kckd: kcpoints(5) = tggd + kcgd
kcpoints(6) = -k + kcqb + kckd: kcpoints(7) = tggd + kcgd - 150
Set kuangche = ThisDrawing.ModelSpace.AddLightWeightPolyline(kcpoints)


'天线
'tainxiangjuguidaomiangaodu
txgd = 1900
txcd = 1000
Dim tianxian As AcadLWPolyline
Dim txpoints(0 To 7) As Double
txpoints(0) = -k + kcqb + 1 / 2 * kckd - 1 / 2 * txcd - 50: txpoints(1) = txgd + tggd - 50
txpoints(2) = -k + kcqb + 1 / 2 * kckd - 1 / 2 * txcd: txpoints(3) = txgd + tggd
txpoints(4) = -k + kcqb + 1 / 2 * kckd - 1 / 2 * txcd + txcd: txpoints(5) = txgd + tggd
txpoints(6) = -k + kcqb + 1 / 2 * kckd - 1 / 2 * txcd + txcd + 50: txpoints(7) = txgd + tggd - 50

Set tianxian = ThisDrawing.ModelSpace.AddLightWeightPolyline(txpoints)




'轨道

' 枕木长度等于矿车宽度kckd  厚度=150 铁轨比枕木高75 与墙壁的距离与矿车对应kcqb

Dim zhenmu  As AcadLWPolyline
Dim zmpoints(0 To 9) As Double
zmpoints(0) = -k + kcqb: zmpoints(1) = tggd - 75
zmpoints(2) = -k + kcqb: zmpoints(3) = tggd - 75 - 150
zmpoints(4) = -k + kcqb + kckd: zmpoints(5) = tggd - 75 - 150
zmpoints(6) = -k + kcqb + kckd: zmpoints(7) = tggd - 75 - 150 + 150
zmpoints(8) = -k + kcqb: zmpoints(9) = tggd - 75

Set zhenmu = ThisDrawing.ModelSpace.AddLightWeightPolyline(zmpoints)


'tieguikuangdu
tgkd = 600


Dim tiegui As AcadLWPolyline
Dim tgpoint(0 To 7) As Double
tgpoint(0) = -k + kcqb + 1 / 2 * kckd - 1 / 2 * tgkd: tgpoint(1) = tggd - 75
tgpoint(2) = -k + kcqb + 1 / 2 * kckd - 1 / 2 * tgkd: tgpoint(3) = tggd
tgpoint(4) = -k + kcqb + 1 / 2 * kckd - 1 / 2 * tgkd - 20: tgpoint(5) = tggd
tgpoint(6) = -k + kcqb + 1 / 2 * kckd - 1 / 2 * tgkd + 20: tgpoint(7) = tggd

Set tiegui = ThisDrawing.ModelSpace.AddLightWeightPolyline(tgpoint)
Dim tiegui2 As AcadLWPolyline
Dim tg2point(0 To 7) As Double
tg2point(0) = -k + kcqb + 1 / 2 * kckd - 1 / 2 * tgkd + tgkd: tg2point(1) = tggd - 75
tg2point(2) = -k + kcqb + 1 / 2 * kckd - 1 / 2 * tgkd + tgkd: tg2point(3) = tggd
tg2point(4) = -k + kcqb + 1 / 2 * kckd - 1 / 2 * tgkd - 20 + tgkd: tg2point(5) = tggd
tg2point(6) = -k + kcqb + 1 / 2 * kckd - 1 / 2 * tgkd + 20 + tgkd: tg2point(7) = tggd

Set tiegui2 = ThisDrawing.ModelSpace.AddLightWeightPolyline(tg2point)




'镜像轴(天线 矿车 枕木 铁轨）
Dim zhoupoint3(0 To 2) As Double
Dim zhoupoint4(0 To 2) As Double
zhoupoint3(0) = -k + kcqb + kckd + 1 / 2 * kcjj: zhoupoint3(1) = 0: zhoupoint3(2) = 0
zhoupoint4(0) = -k + kcqb + kckd + 1 / 2 * kcjj: zhoupoint4(1) = 10: zhoupoint4(2) = 0


' 镜像（天线 矿车 枕木 铁轨）
Dim mirrortianxian As AcadLWPolyline
Set mirrortianxian = tianxian.Mirror(zhoupoint3, zhoupoint4)


Dim mirrorkuangche As AcadLWPolyline
Set mirrorkuangche = kuangche.Mirror(zhoupoint3, zhoupoint4)

Dim mirrorguidao As AcadLWPolyline
Set mirrorzhenmu = zhenmu.Mirror(zhoupoint3, zhoupoint4)


Dim mirrortiegui As AcadLWPolyline
Set mirrortiegui = tiegui.Mirror(zhoupoint3, zhoupoint4)


Dim mirror2tiegui2 As AcadLWPolyline
Set mirror2tiegui2 = tiegui2.Mirror(zhoupoint3, zhoupoint4)

tianxian.color = acBlue
mirrortianxian.color = acBlue
kuangche.color = acBlue
mirrorkuangche.color = acBlue
zhenmu.color = acBlue
mirrorzhenmu.color = acBlue




'道砟

Dim dz1  As AcadLWPolyline
Dim dz1points(0 To 3) As Double
dz1points(0) = -k: dz1points(1) = 150
dz1points(2) = -k + kcqb: dz1points(3) = 150
Set dz1 = ThisDrawing.ModelSpace.AddLightWeightPolyline(dz1points)

Dim dz2  As AcadLWPolyline
Dim dz2points(0 To 3) As Double
dz2points(0) = -k + kcqb + kckd: dz2points(1) = 150
dz2points(2) = -k + kcqb + kckd + kcjj: dz2points(3) = 150
Set dz2 = ThisDrawing.ModelSpace.AddLightWeightPolyline(dz2points)

Dim dz3  As AcadLWPolyline
Dim dz3points(0 To 7) As Double
dz3points(0) = -k + kcqb + kckd + kcjj + kckd: dz3points(1) = 150
dz3points(2) = k - 450: dz3points(3) = 150
dz3points(4) = k - 400: dz3points(5) = 50
dz3points(6) = k: dz3points(7) = 50
Set dz3 = ThisDrawing.ModelSpace.AddLightWeightPolyline(dz3points)


'电线

Dim dxyx(0 To 2) As Double
Dim dxbj1 As Double
Dim dxbj2 As Double
dxyx(0) = k - 300
dxyx(1) = g + 200
dxyx(2) = 0
dxbj1 = 100
dxbj2 = 130
Dim dx3points(0 To 3) As Double
dx3points(0) = k - 300: dx3points(1) = g + 200 + dxbj2
dx3points(2) = k - 200: dx3points(3) = g + 200 + dxbj2 + 600

Set dianxian = ThisDrawing.ModelSpace.AddCircle(dxyx, dxbj1)

 
Set dianxian2 = ThisDrawing.ModelSpace.AddCircle(dxyx, dxbj2)
Set dianxian3 = ThisDrawing.ModelSpace.AddLightWeightPolyline(dx3points)

'标注

'铁轨宽度
Dim bztg As AcadDimAligned
Dim bztgpointsq(0 To 2) As Double
Dim bztgpointsz(0 To 2) As Double
Dim bztgwzpointsz(0 To 2) As Double

bztgpointsq(0) = -k + kcqb + 1 / 2 * kckd - 1 / 2 * tgkd
bztgpointsq(1) = tggd
bztgpointsq(2) = 0
bztgpointsz(0) = -k + kcqb + 1 / 2 * kckd - 1 / 2 * tgkd + tgkd
bztgpointsz(1) = tggd
bztgpointsz(2) = 0
bztgwzpointsz(0) = 0
bztgwzpointsz(1) = 400
bztgwzpointsz(2) = 0
Set bztg = ThisDrawing.ModelSpace.AddDimAligned(bztgpointsq, bztgpointsz, bztgwzpointsz)

'巷道净宽
Dim bzhdjk As AcadDimAligned
Dim bzhdjkpointsq(0 To 2) As Double
Dim bzhdjkpointsz(0 To 2) As Double
Dim bzhdjkwzpointsz(0 To 2) As Double

bzhdjkpointsq(0) = -k
bzhdjkpointsq(1) = 0
bzhdjkpointsq(2) = 0
bzhdjkpointsz(0) = k
bzhdjkpointsz(1) = 0
bzhdjkpointsz(2) = 0
bzhdjkwzpointsz(0) = 0
bzhdjkwzpointsz(1) = -600
bzhdjkwzpointsz(2) = 0
Set bzhdjk = ThisDrawing.ModelSpace.AddDimAligned(bzhdjkpointsq, bzhdjkpointsz, bzhdjkwzpointsz)
'巷道壁高
Dim bzhdbg As AcadDimAligned
Dim bzhdbgpointsq(0 To 2) As Double
Dim bzhdbgpointsz(0 To 2) As Double
Dim bzhdbgwzpointsz(0 To 2) As Double

bzhdbgpointsq(0) = k + h
bzhdbgpointsq(1) = 0
bzhdbgpointsq(2) = 0
bzhdbgpointsz(0) = k + h
bzhdbgpointsz(1) = g
bzhdbgpointsz(2) = 0
bzhdbgwzpointsz(0) = k + h + 200
bzhdbgwzpointsz(1) = 0
bzhdbgwzpointsz(2) = 0
Set bzhdbg = ThisDrawing.ModelSpace.AddDimAligned(bzhdbgpointsq, bzhdbgpointsz, bzhdbgwzpointsz)
'水沟深度

Dim bzsgsd As AcadDimAligned
Dim bzsgsdpointsq(0 To 2) As Double
Dim bzsgsdpointsz(0 To 2) As Double
Dim bzsgsdwzpointsz(0 To 2) As Double

bzsgsdpointsq(0) = k + h
bzsgsdpointsq(1) = -400
bzsgsdpointsq(2) = 0
bzsgsdpointsz(0) = k + h
bzsgsdpointsz(1) = 0
bzsgsdpointsz(2) = 0
bzsgsdwzpointsz(0) = k + h + 200
bzsgsdwzpointsz(1) = 0
bzsgsdwzpointsz(2) = 0
Set bzsgsd = ThisDrawing.ModelSpace.AddDimAligned(bzsgsdpointsq, bzsgsdpointsz, bzsgsdwzpointsz)



'混凝土深度

Dim bzhntsd As AcadDimAligned
Dim bzhntsdpointsq(0 To 2) As Double
Dim bzhntsdpointsz(0 To 2) As Double
Dim bzhntsdwzpointsz(0 To 2) As Double

bzhntsdpointsq(0) = -k - h
bzhntsdpointsq(1) = -300
bzhntsdpointsq(2) = 0
bzhntsdpointsz(0) = -k - h
bzhntsdpointsz(1) = 0
bzhntsdpointsz(2) = 0
bzhntsdwzpointsz(0) = -k - h - 200
bzhntsdwzpointsz(1) = 0
bzhntsdwzpointsz(2) = 0
Set bzhntsd = ThisDrawing.ModelSpace.AddDimAligned(bzhntsdpointsq, bzhntsdpointsz, bzhntsdwzpointsz)

'铁轨高度

Dim bztggd As AcadDimAligned
Dim bztggdpointsq(0 To 2) As Double
Dim bztggdpointsz(0 To 2) As Double
Dim bztggdwzpointsz(0 To 2) As Double

bztggdpointsq(0) = -k - h
bztggdpointsq(1) = 300
bztggdpointsq(2) = 0
bztggdpointsz(0) = -k - h
bztggdpointsz(1) = 0
bztggdpointsz(2) = 0
bztggdwzpointsz(0) = -k - h - 200
bztggdwzpointsz(1) = 0
bztggdwzpointsz(2) = 0
Set bztggd = ThisDrawing.ModelSpace.AddDimAligned(bztggdpointsq, bztggdpointsz, bztggdwzpointsz)

'矿车高度

Dim bzkcgd As AcadDimAligned
Dim bzkcgdpointsq(0 To 2) As Double
Dim bzkcgdpointsz(0 To 2) As Double
Dim bzkcgdwzpointsz(0 To 2) As Double

bzkcgdpointsq(0) = -k - h
bzkcgdpointsq(1) = 300
bzkcgdpointsq(2) = 0
bzkcgdpointsz(0) = -k - h
bzkcgdpointsz(1) = kcgd + tggd
bzkcgdpointsz(2) = 0
bzkcgdwzpointsz(0) = -k - h - 200
bzkcgdwzpointsz(1) = 0
bzkcgdwzpointsz(2) = 0
Set bzkcgd = ThisDrawing.ModelSpace.AddDimAligned(bzkcgdpointsq, bzkcgdpointsz, bzkcgdwzpointsz)
'天线高度

Dim bztxgd As AcadDimAligned
Dim bztxgdpointsq(0 To 2) As Double
Dim bztxgdpointsz(0 To 2) As Double
Dim bztxgdwzpointsz(0 To 2) As Double

bztxgdpointsq(0) = -k - h
bztxgdpointsq(1) = 300
bztxgdpointsq(2) = 0
bztxgdpointsz(0) = -k - h
bztxgdpointsz(1) = txgd + tggd
bztxgdpointsz(2) = 0
bztxgdwzpointsz(0) = -k - h - 400
bztxgdwzpointsz(1) = 0
bztxgdwzpointsz(2) = 0
Set bztxgd = ThisDrawing.ModelSpace.AddDimAligned(bztxgdpointsq, bztxgdpointsz, bztxgdwzpointsz)

'矿车与墙壁间距

Dim bzkcqb As AcadDimAligned
Dim bzkcqbpointsq(0 To 2) As Double
Dim bzkcqbpointsz(0 To 2) As Double
Dim bzkcqbwzpointsz(0 To 2) As Double

bzkcqbpointsq(0) = -k
bzkcqbpointsq(1) = tggd + kcgd - 150
bzkcqbpointsq(2) = 0
bzkcqbpointsz(0) = -k + kcqb
bzkcqbpointsz(1) = tggd + kcgd - 150
bzkcqbpointsz(2) = 0
bzkcqbwzpointsz(0) = 0
bzkcqbwzpointsz(1) = tggd + kcgd - 150
bzkcqbwzpointsz(2) = 0
Set bzkcqb = ThisDrawing.ModelSpace.AddDimAligned(bzkcqbpointsq, bzkcqbpointsz, bzkcqbwzpointsz)
'矿车宽度

Dim bzkckd As AcadDimAligned
Dim bzkckdpointsq(0 To 2) As Double
Dim bzkckdpointsz(0 To 2) As Double
Dim bzkckdwzpointsz(0 To 2) As Double

bzkckdpointsq(0) = -k + kcqb
bzkckdpointsq(1) = tggd + kcgd - 150
bzkckdpointsq(2) = 0
bzkckdpointsz(0) = -k + kcqb + kckd
bzkckdpointsz(1) = tggd + kcgd - 150
bzkckdpointsz(2) = 0
bzkckdwzpointsz(0) = 0
bzkckdwzpointsz(1) = tggd + kcgd - 150
bzkckdwzpointsz(2) = 0
Set bzkckd = ThisDrawing.ModelSpace.AddDimAligned(bzkckdpointsq, bzkckdpointsz, bzkckdwzpointsz)
'矿车间距

Dim bzkcjj As AcadDimAligned
Dim bzkcjjpointsq(0 To 2) As Double
Dim bzkcjjpointsz(0 To 2) As Double
Dim bzkcjjwzpointsz(0 To 2) As Double

bzkcjjpointsq(0) = -k + kcqb + kckd
bzkcjjpointsq(1) = tggd + kcgd - 150
bzkcjjpointsq(2) = 0
bzkcjjpointsz(0) = -k + kcqb + kckd + kcjj
bzkcjjpointsz(1) = tggd + kcgd - 150
bzkcjjpointsz(2) = 0
bzkcjjwzpointsz(0) = 0
bzkcjjwzpointsz(1) = tggd + kcgd - 150
bzkcjjwzpointsz(2) = 0
Set bzkcjj = ThisDrawing.ModelSpace.AddDimAligned(bzkcjjpointsq, bzkcjjpointsz, bzkcjjwzpointsz)

'巷道壁厚
Dim bzhdbh As AcadDimAligned
Dim bzhdbhpointsq(0 To 2) As Double
Dim bzhdbhpointsz(0 To 2) As Double
Dim bzhdbhwzpointsz(0 To 2) As Double

bzhdbhpointsq(0) = -k - h
bzhdbhpointsq(1) = 0
bzhdbhpointsq(2) = 0
bzhdbhpointsz(0) = -k
bzhdbhpointsz(1) = 0
bzhdbhpointsz(2) = 0
bzhdbhwzpointsz(0) = 0
bzhdbhwzpointsz(1) = bzhdjkwzpointsz(1)
bzhdbhwzpointsz(2) = 0
Set bzhdbh = ThisDrawing.ModelSpace.AddDimAligned(bzhdbhpointsq, bzhdbhpointsz, bzhdbhwzpointsz)



End Sub

 '自创建标注样式
Public Function AddDimStyle1()
    Dim dimStyle As AcadDimStyle
    Set dimStyle = ThisDrawing.DimStyles.Add("dimStyle1")
    ThisDrawing.ActiveDimStyle = dimStyle '激活该标注样式
   
   With ThisDrawing
       '第一组定义全局和线性比例因子
         .SetVariable "DimScale", 1     '设置全局比例因子
         .SetVariable "DimLFac", 1   '线性比例因子. '1'=1:1, '2'=2:1,'.5'=1:2等
        '定义典型的标注特性
        .SetVariable "DimADec", 0      '控制角度标注的显示精确位数
        .SetVariable "DimAssoc", 2     '控制标注对象的关联性
                                       '实际上该系统变量由图形控制
        .SetVariable "DimASz", 50        '控制尺寸线、引线箭头的大小。并控制钩线的大小
        .SetVariable "DimAtFit", 3    '当尺寸界线的空间不足以同时放下标注文字和箭头时,确定这两者的排列方式
                                        '0 将文字和箭头均放置于尺寸界线之外
                                        '1  先移动箭头，然后移动文字
                                        '2  先移动文字，然后移动箭头
                                        '3  移动文字和箭头中较合适的一个
        .SetVariable "DimAUnit", 0     '设置角度标注的单位格式
                                       '0 十进制度数
        .SetVariable "DimAZin", 0      '对角度标注作消零处理
                                       '0 显示所有前导零和后续零
        .SetVariable "DimBlk", ""      '设置尺寸线或引线末端显示的箭头块
                                       '"" 实心闭合
        .SetVariable "DimBlk1", "."     '当 DIMSAH 系统变量打开时，设置尺寸线第一个端点的箭头
        .SetVariable "DimBlk2", "."     '当 DIMSAH 系统变量打开时，设置尺寸线第二个端点的箭头
        .SetVariable "DimClrD", 256     '为尺寸线、箭头和标注引线指定颜色
        .SetVariable "DimClrE", 256    '为尺寸界线指定颜色。此颜色可以是任意有效的颜色编号
        .SetVariable "DimClrT", 256     '为标注文字指定颜色
         .SetVariable "DimDec", 0       '设置标注主单位显示的小数位位数
        .SetVariable "DimExe", 10        '指定尺寸界线超出尺寸线的距离
        .SetVariable "DimExO", 0       '指定尺寸界线偏移原点的距离
        .SetVariable "DimFrac", 0      '在 DIMLUNIT 系统变量设置为 4（建筑）或 5（分数）时设置分数格式
        .SetVariable "DimGap", 0.5     '当尺寸线分成段以在两段之间放置标注文字时，设置标注文字周围的距离
        .SetVariable "DimJust", 0      '控制标注文字的水平位置
                                        '0  将文字置于尺寸线之上，并在尺寸界线之间置中对正
                                        '1  紧邻第一条尺寸界线放置标注文字
                                        '2  紧邻第二条尺寸界线放置标注文字
                                        '3  将标注文字放在第一条尺寸界线以上，并与之对齐
                                        '4  将标注文字放在第二条尺寸界线以上，并与之对齐
        .SetVariable "DimLwd", acLnWtByLayer '指定尺寸线的线宽
        .SetVariable "DimLwe", acLnWtByLayer '指定尺寸界线的线宽
        .SetVariable "DimPost", ""     '指定标注测量值的文字前缀或后缀（或者两者都指定）
        .SetVariable "DimRnd", 0       '将所有标注距离舍入到指定值
        .SetVariable "DimSAh", 1       '控制尺寸线箭头块的显示
        .SetVariable "DimSD1", 0       '控制是否禁止显示第一条尺寸线
        .SetVariable "DimSD2", 0       '控制是否禁止显示第二条尺寸线
        .SetVariable "DimSE1", 0       '控制是否禁止显示第一条尺寸界线
        .SetVariable "DimSE2", 0       '控制是否禁止显示第二条尺寸界线
        .SetVariable "DimSOXD", 0      '控制是否允许尺寸线绘制到尺寸界线之外
        .SetVariable "DimTAD", 0       '控制文字相对尺寸线的垂直位置
                                       '0 标注文字在尺寸界线之间居中放置
                                        '1  除非尺寸线不是水平放置的或者尺寸界线内的文字被强制为水平放置
                                        '(DIMTIH = 1)，否则就将标注文字放置在尺寸线的上方。标注文字最底部
                                        '基线到尺寸线的距离值就是系统变量DIMGAP 的当前值。
        .SetVariable "DimTIH", 0       '控制所有标注类型（坐标标注除外）的标注文字在尺寸界线内的位置
                                        '0 或关 将文字与尺寸线对齐
                                        '1 或开 将文字水平放置
        .SetVariable "DimTIX", 1      '在尺寸界线之间绘制文字
                                        '0 或关 结果随标注类型的不同而不同。对于线性和角度标注，AutoCAD
                                        '将文字放置到尺寸界线之间（如果有足够的空间）。对于不适于放入圆
                                        '或圆弧中的半径标注和直径标注，DIMTIX 无效并总是强制将文字放到圆或圆弧之外
                                        '1 或开 将标注文字绘制在尺寸界线之间，即使 AutoCAD 通常将这些文字放置于尺寸界线之外。
        .SetVariable "DimTMOVE", 2      '设置标注文字的移动规则
                                        '0  尺寸线和标注文字一起移动
                                        '1  在移动标注文字时添加一条引线
                                        '2  允许标注文字自由移动而不用添加引线
        .SetVariable "DimTOFL", 0      '控制是否将尺寸线绘制在尺寸界线之间（即使文字放置在尺寸界线之外）
        .SetVariable "DimTOH", 0       '控制标注文字在尺寸界线外的位置
        .SetVariable "DimTSz", 0      '指定线性标注、半径标注以及直径标注中替代箭头的小斜线尺寸
        .SetVariable "DimTVP", 1        '控制尺寸线上方或下方标注文字的垂直位置
        .SetVariable "DimTxSty", "STANDARD"     '指定标注的文字样式
        .SetVariable "DimTxt", 50         '指定标注文字的高度，除非当前文字样式具有固定的高度
        .SetVariable "DimUPT", 0        '控制用户定位文字的选项
        .SetVariable "DimZIn", 0        '控制是否对主单位值作消零处理
'
       '定义换算单位的特性
        .SetVariable "DimAlt", 0        '控制标注中换算单位的显示
        .SetVariable "DimAltD", 4       '控制换算单位中小数位的位数
        .SetVariable "DimAltF", 25.4    '控制换算单位乘数
        .SetVariable "DimAltRnd", 0     '舍入换算标注单位
        .SetVariable "DimAltTD", 4      '设置标注换算单位公差值小数位的位数
        .SetVariable "DimAltTZ", 0      '控制是否对公差值作消零处理
        .SetVariable "DimAltU", 2       '为所有标注样式族（角度标注除外）换算单位设置单位格式
        .SetVariable "DimAltZ", 0       '控制是否对换算单位标注值作消零处理
        .SetVariable "DimAPost", ""     '为所有标注类型（角度标注除外）的换算标注测量值指定文字前缀或后缀（或两者都指定）
        
        
   End With
    '标注样式的特性从图形已有样式中获得
   dimStyle.CopyFrom ThisDrawing
   
     
End Function

Attribute VB_Name = "UserForm1"
Attribute VB_Base = "0{C5E9E7D3-6509-44C8-BFFF-28BF63380203}{91DDC109-B06C-4943-9835-C12937668D4F}"
Attribute VB_GlobalNameSpace = False
Attribute VB_Creatable = False
Attribute VB_PredeclaredId = True
Attribute VB_Exposed = False
Attribute VB_TemplateDerived = False
Attribute VB_Customizable = False

Private Sub ComboBox1_Change()

End Sub

'生成巷道
Private Sub CommandButton1_Click()

a1 = Val(TextBox1.Text) '净宽
a2 = Val(TextBox2.Text) '壁高
a3 = Val(TextBox3.Text) '壁厚

k = a1 / 2
g = a2
h = a3


'矿车与墙壁距离
kcqb = 300
'矿车间距
kcjj = 300
'矿车宽度
kckd = 1250
'矿车高度
kcgd = 1300
'铁轨高度
tggd = 300
'天线高度
txgd = 1900
'天线长度
txcd = 1000

If OptionButton1.Value = True Then

'半圆
Dim yuan1 As AcadArc
Dim yuan1xin(0 To 2) As Double
Dim yuan1banjing As Double
Dim yuan1qsjd  As Double
Dim yuan1zzjd As Double
yuan1xin(0) = 0: yuan1xin(1) = g: yuan1xin(2) = 0
yuan1banjing = k
yuan1qsjd = 0
yuan1zzjd = 3.15
Set yuan1 = ThisDrawing.ModelSpace.AddArc(yuan1xin, yuan1banjing, yuan1qsjd, yuan1zzjd)

Dim yuan2 As AcadArc
Dim yuan2xin(0 To 2) As Double
Dim yuan2banjing As Double
Dim yuan2qsjd  As Double
Dim yuan2zzjd As Double
yuan2xin(0) = 0: yuan2xin(1) = g: yuan2xin(2) = 0
yuan2banjing = k + h
yuan2qsjd = 0
yuan2zzjd = 3.15
Set yuan2 = ThisDrawing.ModelSpace.AddArc(yuan2xin, yuan2banjing, yuan2qsjd, yuan2zzjd)

ElseIf OptionButton1.Value = True Then

'三心拱
Dim syuanhu1 As AcadArc
Dim syuanhu1xin(0 To 2) As Double
Dim syuanhu1banjing As Double
Dim syuanhu1qsjd  As Double
Dim syuanhu1zzjd As Double
syuanhu1xin(0) = 0: syuanhu1xin(1) = g - k / 1.732: syuanhu1xin(2) = 0
syuanhu1banjing = k / 1.732 * 2
syuanhu1qsjd = 0.52
syuanhu1zzjd = 2.62
Set syuanhu1 = ThisDrawing.ModelSpace.AddArc(syuanhu1xin, syuanhu1banjing, syuanhu1qsjd, syuanhu1zzjd)

Dim syuanhu2 As AcadArc
Dim syuanhu2xin(0 To 2) As Double
Dim syuanhu2banjing As Double
Dim syuanhu2qsjd  As Double
Dim syuanhu2zzjd As Double
syuanhu2xin(0) = 0: syuanhu2xin(1) = g - k / 1.732: syuanhu2xin(2) = 0
syuanhu2banjing = k / 1.732 * 2 + 180
syuanhu2qsjd = 0.48
syuanhu2zzjd = 2.66
Set syuanhu2 = ThisDrawing.ModelSpace.AddArc(syuanhu2xin, syuanhu2banjing, syuanhu2qsjd, syuanhu2zzjd)


Else: d = 3

'圆弧
Dim yuanhu1 As AcadArc
Dim yuanhu1xin(0 To 2) As Double
Dim yuanhu1banjing As Double
Dim yuanhu1qsjd  As Double
Dim yuanhu1zzjd As Double
yuanhu1xin(0) = 0: yuanhu1xin(1) = g - k / 1.732: yuanhu1xin(2) = 0
yuanhu1banjing = k / 1.732 * 2
yuanhu1qsjd = 0.52
yuanhu1zzjd = 2.62
Set yuanhu1 = ThisDrawing.ModelSpace.AddArc(yuanhu1xin, yuanhu1banjing, yuanhu1qsjd, yuanhu1zzjd)

Dim yuanhu2 As AcadArc
Dim yuanhu2xin(0 To 2) As Double
Dim yuanhu2banjing As Double
Dim yuanhu2qsjd  As Double
Dim yuanhu2zzjd As Double
yuanhu2xin(0) = 0: yuanhu2xin(1) = g - k / 1.732: yuanhu2xin(2) = 0
yuanhu2banjing = k / 1.732 * 2 + 180
yuanhu2qsjd = 0.48
yuanhu2zzjd = 2.66
Set yuanhu2 = ThisDrawing.ModelSpace.AddArc(yuanhu2xin, yuanhu2banjing, yuanhu2qsjd, yuanhu2zzjd)

End If

'右墙
Dim youqiang As AcadLWPolyline
Dim yqpoints(0 To 7) As Double
yqpoints(0) = k: yqpoints(1) = g
yqpoints(2) = k: yqpoints(3) = -400
yqpoints(4) = k + h: yqpoints(5) = -400
yqpoints(6) = k + h: yqpoints(7) = g
Set youqiang = ThisDrawing.ModelSpace.AddLightWeightPolyline(yqpoints)


'左墙
Dim zuoqiang As AcadLWPolyline
Dim zqpoints(0 To 7) As Double
zqpoints(0) = -k: zqpoints(1) = g
zqpoints(2) = -k: zqpoints(3) = -300
zqpoints(4) = -k - h: zqpoints(5) = -300
zqpoints(6) = -k - h: zqpoints(7) = g
Set zuoqiang = ThisDrawing.ModelSpace.AddLightWeightPolyline(zqpoints)


'地面
Dim di As AcadLWPolyline
Dim dpoints(0 To 3) As Double
dpoints(0) = -k: dpoints(1) = 0
dpoints(2) = k: dpoints(3) = 0
Set di = ThisDrawing.ModelSpace.AddLightWeightPolyline(dpoints)

'水沟
x = 50 '水沟壁厚
Dim dhuigou As AcadLWPolyline
Dim sgpoints(0 To 13) As Double
sgpoints(0) = k - x: sgpoints(1) = 0
sgpoints(2) = k - x: sgpoints(3) = -350
sgpoints(4) = k - x - 300: sgpoints(5) = -350
sgpoints(6) = k - x - 300: sgpoints(7) = 0
sgpoints(8) = k - x - 300 - x: sgpoints(9) = 0
sgpoints(10) = k - x - 300 - x: sgpoints(11) = -350 - x
sgpoints(12) = k: sgpoints(13) = -350 - x
Set shuigou = ThisDrawing.ModelSpace.AddLightWeightPolyline(sgpoints)


'矿车
Dim kuangche  As AcadLWPolyline
Dim kcpoints(0 To 7) As Double
kcpoints(0) = -k + kcqb: kcpoints(1) = tggd + kcgd - 150
kcpoints(2) = -k + kcqb: kcpoints(3) = tggd + kcgd
kcpoints(4) = -k + kcqb + kckd: kcpoints(5) = tggd + kcgd
kcpoints(6) = -k + kcqb + kckd: kcpoints(7) = tggd + kcgd - 150
Set kuangche = ThisDrawing.ModelSpace.AddLightWeightPolyline(kcpoints)


'天线
Dim tianxian As AcadLWPolyline
Dim txpoints(0 To 7) As Double
txpoints(0) = -k + kcqb + 1 / 2 * kckd - 1 / 2 * txcd - 50: txpoints(1) = txgd + tggd - 50
txpoints(2) = -k + kcqb + 1 / 2 * kckd - 1 / 2 * txcd: txpoints(3) = txgd + tggd
txpoints(4) = -k + kcqb + 1 / 2 * kckd - 1 / 2 * txcd + txcd: txpoints(5) = txgd + tggd
txpoints(6) = -k + kcqb + 1 / 2 * kckd - 1 / 2 * txcd + txcd + 50: txpoints(7) = txgd + tggd - 50
Set tianxian = ThisDrawing.ModelSpace.AddLightWeightPolyline(txpoints)

'轨道

' 枕木长度等于矿车宽度kckd  厚度150 铁轨比枕木高75 与墙壁的距离与矿车对应kcqb
Dim zhenmu  As AcadLWPolyline
Dim zmpoints(0 To 9) As Double
zmpoints(0) = -k + kcqb: zmpoints(1) = tggd - 75
zmpoints(2) = -k + kcqb: zmpoints(3) = tggd - 75 - 150
zmpoints(4) = -k + kcqb + kckd: zmpoints(5) = tggd - 75 - 150
zmpoints(6) = -k + kcqb + kckd: zmpoints(7) = tggd - 75 - 150 + 150
zmpoints(8) = -k + kcqb: zmpoints(9) = tggd - 75
Set zhenmu = ThisDrawing.ModelSpace.AddLightWeightPolyline(zmpoints)


'铁轨宽度
tgkd = 600
Dim tiegui As AcadLWPolyline
Dim tgpoint(0 To 7) As Double
tgpoint(0) = -k + kcqb + 1 / 2 * kckd - 1 / 2 * tgkd: tgpoint(1) = tggd - 75
tgpoint(2) = -k + kcqb + 1 / 2 * kckd - 1 / 2 * tgkd: tgpoint(3) = tggd
tgpoint(4) = -k + kcqb + 1 / 2 * kckd - 1 / 2 * tgkd - 20: tgpoint(5) = tggd
tgpoint(6) = -k + kcqb + 1 / 2 * kckd - 1 / 2 * tgkd + 20: tgpoint(7) = tggd
Set tiegui = ThisDrawing.ModelSpace.AddLightWeightPolyline(tgpoint)
Dim tiegui2 As AcadLWPolyline
Dim tg2point(0 To 7) As Double
tg2point(0) = -k + kcqb + 1 / 2 * kckd - 1 / 2 * tgkd + tgkd: tg2point(1) = tggd - 75
tg2point(2) = -k + kcqb + 1 / 2 * kckd - 1 / 2 * tgkd + tgkd: tg2point(3) = tggd
tg2point(4) = -k + kcqb + 1 / 2 * kckd - 1 / 2 * tgkd - 20 + tgkd: tg2point(5) = tggd
tg2point(6) = -k + kcqb + 1 / 2 * kckd - 1 / 2 * tgkd + 20 + tgkd: tg2point(7) = tggd
Set tiegui2 = ThisDrawing.ModelSpace.AddLightWeightPolyline(tg2point)

'镜像轴(天线 矿车 枕木 铁轨）
Dim zhoupoint3(0 To 2) As Double
Dim zhoupoint4(0 To 2) As Double
zhoupoint3(0) = -k + kcqb + kckd + 1 / 2 * kcjj: zhoupoint3(1) = 0: zhoupoint3(2) = 0
zhoupoint4(0) = -k + kcqb + kckd + 1 / 2 * kcjj: zhoupoint4(1) = 10: zhoupoint4(2) = 0


'镜像（天线 矿车 枕木 铁轨）
Dim mirrortianxian As AcadLWPolyline
Set mirrortianxian = tianxian.Mirror(zhoupoint3, zhoupoint4)

Dim mirrorkuangche As AcadLWPolyline
Set mirrorkuangche = kuangche.Mirror(zhoupoint3, zhoupoint4)

Dim mirrorguidao As AcadLWPolyline
Set mirrorzhenmu = zhenmu.Mirror(zhoupoint3, zhoupoint4)

Dim mirrortiegui As AcadLWPolyline
Set mirrortiegui = tiegui.Mirror(zhoupoint3, zhoupoint4)

Dim mirror2tiegui2 As AcadLWPolyline
Set mirror2tiegui2 = tiegui2.Mirror(zhoupoint3, zhoupoint4)

tianxian.color = acBlue
mirrortianxian.color = acBlue
kuangche.color = acBlue
mirrorkuangche.color = acBlue
zhenmu.color = acBlue
mirrorzhenmu.color = acBlue

'道砟面
Dim dz1  As AcadLWPolyline
Dim dz1points(0 To 3) As Double
dz1points(0) = -k: dz1points(1) = 150
dz1points(2) = -k + kcqb: dz1points(3) = 150
Set dz1 = ThisDrawing.ModelSpace.AddLightWeightPolyline(dz1points)

Dim dz2  As AcadLWPolyline
Dim dz2points(0 To 3) As Double
dz2points(0) = -k + kcqb + kckd: dz2points(1) = 150
dz2points(2) = -k + kcqb + kckd + kcjj: dz2points(3) = 150
Set dz2 = ThisDrawing.ModelSpace.AddLightWeightPolyline(dz2points)

Dim dz3  As AcadLWPolyline
Dim dz3points(0 To 7) As Double
dz3points(0) = -k + kcqb + kckd + kcjj + kckd: dz3points(1) = 150
dz3points(2) = k - 450: dz3points(3) = 150
dz3points(4) = k - 400: dz3points(5) = 50
dz3points(6) = k: dz3points(7) = 50
Set dz3 = ThisDrawing.ModelSpace.AddLightWeightPolyline(dz3points)

'电线
Dim dxyx(0 To 2) As Double
Dim dxbj1 As Double
Dim dxbj2 As Double
dxyx(0) = k - 300
dxyx(1) = g + 200
dxyx(2) = 0
dxbj1 = 100
dxbj2 = 130
Dim dx3points(0 To 3) As Double
dx3points(0) = k - 300: dx3points(1) = g + 200 + dxbj2
dx3points(2) = k - 200: dx3points(3) = g + 200 + dxbj2 + 600

Set dianxian = ThisDrawing.ModelSpace.AddCircle(dxyx, dxbj1)
Set dianxian2 = ThisDrawing.ModelSpace.AddCircle(dxyx, dxbj2)
'Set dianxian3 = ThisDrawing.ModelSpace.AddLightWeightPolyline(dx3points)

'标注

'铁轨宽度
Dim bztg As AcadDimAligned
Dim bztgpointsq(0 To 2) As Double
Dim bztgpointsz(0 To 2) As Double
Dim bztgwzpointsz(0 To 2) As Double

bztgpointsq(0) = -k + kcqb + 1 / 2 * kckd - 1 / 2 * tgkd
bztgpointsq(1) = tggd
bztgpointsq(2) = 0
bztgpointsz(0) = -k + kcqb + 1 / 2 * kckd - 1 / 2 * tgkd + tgkd
bztgpointsz(1) = tggd
bztgpointsz(2) = 0
bztgwzpointsz(0) = 0
bztgwzpointsz(1) = 400
bztgwzpointsz(2) = 0
Set bztg = ThisDrawing.ModelSpace.AddDimAligned(bztgpointsq, bztgpointsz, bztgwzpointsz)

'巷道净宽
Dim bzhdjk As AcadDimAligned
Dim bzhdjkpointsq(0 To 2) As Double
Dim bzhdjkpointsz(0 To 2) As Double
Dim bzhdjkwzpointsz(0 To 2) As Double

bzhdjkpointsq(0) = -k
bzhdjkpointsq(1) = 0
bzhdjkpointsq(2) = 0
bzhdjkpointsz(0) = k
bzhdjkpointsz(1) = 0
bzhdjkpointsz(2) = 0
bzhdjkwzpointsz(0) = 0
bzhdjkwzpointsz(1) = -600
bzhdjkwzpointsz(2) = 0
Set bzhdjk = ThisDrawing.ModelSpace.AddDimAligned(bzhdjkpointsq, bzhdjkpointsz, bzhdjkwzpointsz)

'巷道壁高
Dim bzhdbg As AcadDimAligned
Dim bzhdbgpointsq(0 To 2) As Double
Dim bzhdbgpointsz(0 To 2) As Double
Dim bzhdbgwzpointsz(0 To 2) As Double

bzhdbgpointsq(0) = k + h
bzhdbgpointsq(1) = 0
bzhdbgpointsq(2) = 0
bzhdbgpointsz(0) = k + h
bzhdbgpointsz(1) = g
bzhdbgpointsz(2) = 0
bzhdbgwzpointsz(0) = k + h + 200
bzhdbgwzpointsz(1) = 0
bzhdbgwzpointsz(2) = 0
Set bzhdbg = ThisDrawing.ModelSpace.AddDimAligned(bzhdbgpointsq, bzhdbgpointsz, bzhdbgwzpointsz)

'水沟深度
Dim bzsgsd As AcadDimAligned
Dim bzsgsdpointsq(0 To 2) As Double
Dim bzsgsdpointsz(0 To 2) As Double
Dim bzsgsdwzpointsz(0 To 2) As Double

bzsgsdpointsq(0) = k + h
bzsgsdpointsq(1) = -400
bzsgsdpointsq(2) = 0
bzsgsdpointsz(0) = k + h
bzsgsdpointsz(1) = 0
bzsgsdpointsz(2) = 0
bzsgsdwzpointsz(0) = k + h + 200
bzsgsdwzpointsz(1) = 0
bzsgsdwzpointsz(2) = 0
Set bzsgsd = ThisDrawing.ModelSpace.AddDimAligned(bzsgsdpointsq, bzsgsdpointsz, bzsgsdwzpointsz)



'混凝土深度
Dim bzhntsd As AcadDimAligned
Dim bzhntsdpointsq(0 To 2) As Double
Dim bzhntsdpointsz(0 To 2) As Double
Dim bzhntsdwzpointsz(0 To 2) As Double

bzhntsdpointsq(0) = -k - h
bzhntsdpointsq(1) = -300
bzhntsdpointsq(2) = 0
bzhntsdpointsz(0) = -k - h
bzhntsdpointsz(1) = 0
bzhntsdpointsz(2) = 0
bzhntsdwzpointsz(0) = -k - h - 200
bzhntsdwzpointsz(1) = 0
bzhntsdwzpointsz(2) = 0
Set bzhntsd = ThisDrawing.ModelSpace.AddDimAligned(bzhntsdpointsq, bzhntsdpointsz, bzhntsdwzpointsz)

'铁轨高度
Dim bztggd As AcadDimAligned
Dim bztggdpointsq(0 To 2) As Double
Dim bztggdpointsz(0 To 2) As Double
Dim bztggdwzpointsz(0 To 2) As Double

bztggdpointsq(0) = -k - h
bztggdpointsq(1) = 300
bztggdpointsq(2) = 0
bztggdpointsz(0) = -k - h
bztggdpointsz(1) = 0
bztggdpointsz(2) = 0
bztggdwzpointsz(0) = -k - h - 200
bztggdwzpointsz(1) = 0
bztggdwzpointsz(2) = 0
Set bztggd = ThisDrawing.ModelSpace.AddDimAligned(bztggdpointsq, bztggdpointsz, bztggdwzpointsz)

'矿车高度
Dim bzkcgd As AcadDimAligned
Dim bzkcgdpointsq(0 To 2) As Double
Dim bzkcgdpointsz(0 To 2) As Double
Dim bzkcgdwzpointsz(0 To 2) As Double

bzkcgdpointsq(0) = -k - h
bzkcgdpointsq(1) = 300
bzkcgdpointsq(2) = 0
bzkcgdpointsz(0) = -k - h
bzkcgdpointsz(1) = kcgd + tggd
bzkcgdpointsz(2) = 0
bzkcgdwzpointsz(0) = -k - h - 200
bzkcgdwzpointsz(1) = 0
bzkcgdwzpointsz(2) = 0
Set bzkcgd = ThisDrawing.ModelSpace.AddDimAligned(bzkcgdpointsq, bzkcgdpointsz, bzkcgdwzpointsz)

'天线高度
Dim bztxgd As AcadDimAligned
Dim bztxgdpointsq(0 To 2) As Double
Dim bztxgdpointsz(0 To 2) As Double
Dim bztxgdwzpointsz(0 To 2) As Double

bztxgdpointsq(0) = -k - h
bztxgdpointsq(1) = 300
bztxgdpointsq(2) = 0
bztxgdpointsz(0) = -k - h
bztxgdpointsz(1) = txgd + tggd
bztxgdpointsz(2) = 0
bztxgdwzpointsz(0) = -k - h - 400
bztxgdwzpointsz(1) = 0
bztxgdwzpointsz(2) = 0
Set bztxgd = ThisDrawing.ModelSpace.AddDimAligned(bztxgdpointsq, bztxgdpointsz, bztxgdwzpointsz)

'矿车与墙壁间距
Dim bzkcqb As AcadDimAligned
Dim bzkcqbpointsq(0 To 2) As Double
Dim bzkcqbpointsz(0 To 2) As Double
Dim bzkcqbwzpointsz(0 To 2) As Double

bzkcqbpointsq(0) = -k
bzkcqbpointsq(1) = tggd + kcgd - 150
bzkcqbpointsq(2) = 0
bzkcqbpointsz(0) = -k + kcqb
bzkcqbpointsz(1) = tggd + kcgd - 150
bzkcqbpointsz(2) = 0
bzkcqbwzpointsz(0) = 0
bzkcqbwzpointsz(1) = tggd + kcgd - 150
bzkcqbwzpointsz(2) = 0
Set bzkcqb = ThisDrawing.ModelSpace.AddDimAligned(bzkcqbpointsq, bzkcqbpointsz, bzkcqbwzpointsz)

'矿车宽度
Dim bzkckd As AcadDimAligned
Dim bzkckdpointsq(0 To 2) As Double
Dim bzkckdpointsz(0 To 2) As Double
Dim bzkckdwzpointsz(0 To 2) As Double

bzkckdpointsq(0) = -k + kcqb
bzkckdpointsq(1) = tggd + kcgd - 150
bzkckdpointsq(2) = 0
bzkckdpointsz(0) = -k + kcqb + kckd
bzkckdpointsz(1) = tggd + kcgd - 150
bzkckdpointsz(2) = 0
bzkckdwzpointsz(0) = 0
bzkckdwzpointsz(1) = tggd + kcgd - 150
bzkckdwzpointsz(2) = 0
Set bzkckd = ThisDrawing.ModelSpace.AddDimAligned(bzkckdpointsq, bzkckdpointsz, bzkckdwzpointsz)

'矿车间距
Dim bzkcjj As AcadDimAligned
Dim bzkcjjpointsq(0 To 2) As Double
Dim bzkcjjpointsz(0 To 2) As Double
Dim bzkcjjwzpointsz(0 To 2) As Double

bzkcjjpointsq(0) = -k + kcqb + kckd
bzkcjjpointsq(1) = tggd + kcgd - 150
bzkcjjpointsq(2) = 0
bzkcjjpointsz(0) = -k + kcqb + kckd + kcjj
bzkcjjpointsz(1) = tggd + kcgd - 150
bzkcjjpointsz(2) = 0
bzkcjjwzpointsz(0) = 0
bzkcjjwzpointsz(1) = tggd + kcgd - 150
bzkcjjwzpointsz(2) = 0
Set bzkcjj = ThisDrawing.ModelSpace.AddDimAligned(bzkcjjpointsq, bzkcjjpointsz, bzkcjjwzpointsz)

'巷道壁厚
Dim bzhdbh As AcadDimAligned
Dim bzhdbhpointsq(0 To 2) As Double
Dim bzhdbhpointsz(0 To 2) As Double
Dim bzhdbhwzpointsz(0 To 2) As Double

bzhdbhpointsq(0) = -k - h
bzhdbhpointsq(1) = 0
bzhdbhpointsq(2) = 0
bzhdbhpointsz(0) = -k
bzhdbhpointsz(1) = 0
bzhdbhpointsz(2) = 0
bzhdbhwzpointsz(0) = 0
bzhdbhwzpointsz(1) = bzhdjkwzpointsz(1)
bzhdbhwzpointsz(2) = 0
Set bzhdbh = ThisDrawing.ModelSpace.AddDimAligned(bzhdbhpointsq, bzhdbhpointsz, bzhdbhwzpointsz)



End Sub

Private Sub CommandButton2_Click()
Unload Me
End Sub

Private Sub Label1_Click()

End Sub

Private Sub OptionButton1_Click()

End Sub



Private Sub OptionButton2_Click()

End Sub

Private Sub UserForm_Activate()
ComboBox1.List = Array("单轨", "双轨")


'自定义标注格式

Dim dimStyle As AcadDimStyle
    Set dimStyle = ThisDrawing.DimStyles.Add("dimStyle1")
    ThisDrawing.ActiveDimStyle = dimStyle '激活该标注样式
   
   With ThisDrawing
       '第一组定义全局和线性比例因子
         .SetVariable "DimScale", 1     '设置全局比例因子
         .SetVariable "DimLFac", 1   '线性比例因子. '1'=1:1, '2'=2:1,'.5'=1:2等
        '定义典型的标注特性
        .SetVariable "DimADec", 0      '控制角度标注的显示精确位数
        .SetVariable "DimAssoc", 2     '控制标注对象的关联性
                                       '实际上该系统变量由图形控制
        .SetVariable "DimASz", 70        '控制尺寸线、引线箭头的大小。并控制钩线的大小
        .SetVariable "DimAtFit", 3    '当尺寸界线的空间不足以同时放下标注文字和箭头时,确定这两者的排列方式
                                        '0 将文字和箭头均放置于尺寸界线之外
                                        '1  先移动箭头，然后移动文字
                                        '2  先移动文字，然后移动箭头
                                        '3  移动文字和箭头中较合适的一个
        .SetVariable "DimAUnit", 0     '设置角度标注的单位格式
                                       '0 十进制度数
        .SetVariable "DimAZin", 0      '对角度标注作消零处理
                                       '0 显示所有前导零和后续零
        .SetVariable "DimBlk", ""      '设置尺寸线或引线末端显示的箭头块
                                       '"" 实心闭合
        .SetVariable "DimBlk1", ""     '当 DIMSAH 系统变量打开时，设置尺寸线第一个端点的箭头
        .SetVariable "DimBlk2", ""     '当 DIMSAH 系统变量打开时，设置尺寸线第二个端点的箭头
        .SetVariable "DimClrD", 2     '为尺寸线、箭头和标注引线指定颜色
        .SetVariable "DimClrE", 2    '为尺寸界线指定颜色。此颜色可以是任意有效的颜色编号
        .SetVariable "DimClrT", 2     '为标注文字指定颜色
         .SetVariable "DimDec", 0       '设置标注主单位显示的小数位位数
        .SetVariable "DimExe", 0        '指定尺寸界线超出尺寸线的距离
        .SetVariable "DimExO", 0       '指定尺寸界线偏移原点的距离
        .SetVariable "DimFrac", 0      '在 DIMLUNIT 系统变量设置为 4（建筑）或 5（分数）时设置分数格式
        .SetVariable "DimGap", 0.5     '当尺寸线分成段以在两段之间放置标注文字时，设置标注文字周围的距离
        .SetVariable "DimJust", 0      '控制标注文字的水平位置
                                        '0  将文字置于尺寸线之上，并在尺寸界线之间置中对正
                                        '1  紧邻第一条尺寸界线放置标注文字
                                        '2  紧邻第二条尺寸界线放置标注文字
                                        '3  将标注文字放在第一条尺寸界线以上，并与之对齐
                                        '4  将标注文字放在第二条尺寸界线以上，并与之对齐
        .SetVariable "DimLwd", acLnWtByLayer '指定尺寸线的线宽
        .SetVariable "DimLwe", acLnWtByLayer '指定尺寸界线的线宽
        .SetVariable "DimPost", ""     '指定标注测量值的文字前缀或后缀（或者两者都指定）
        .SetVariable "DimRnd", 0       '将所有标注距离舍入到指定值
        .SetVariable "DimSAh", 0       '控制尺寸线箭头块的显示
        .SetVariable "DimSD1", 0       '控制是否禁止显示第一条尺寸线
        .SetVariable "DimSD2", 0       '控制是否禁止显示第二条尺寸线
        .SetVariable "DimSE1", 0       '控制是否禁止显示第一条尺寸界线
        .SetVariable "DimSE2", 0       '控制是否禁止显示第二条尺寸界线
        .SetVariable "DimSOXD", 0      '控制是否允许尺寸线绘制到尺寸界线之外
        .SetVariable "DimTAD", 0       '控制文字相对尺寸线的垂直位置
                                       '0 标注文字在尺寸界线之间居中放置
                                        '1  除非尺寸线不是水平放置的或者尺寸界线内的文字被强制为水平放置
                                        '(DIMTIH = 1)，否则就将标注文字放置在尺寸线的上方。标注文字最底部
                                        '基线到尺寸线的距离值就是系统变量DIMGAP 的当前值。
        .SetVariable "DimTIH", 0       '控制所有标注类型（坐标标注除外）的标注文字在尺寸界线内的位置
                                        '0 或关 将文字与尺寸线对齐
                                        '1 或开 将文字水平放置
        .SetVariable "DimTIX", 1      '在尺寸界线之间绘制文字
                                        '0 或关 结果随标注类型的不同而不同。对于线性和角度标注，AutoCAD
                                        '将文字放置到尺寸界线之间（如果有足够的空间）。对于不适于放入圆
                                        '或圆弧中的半径标注和直径标注，DIMTIX 无效并总是强制将文字放到圆或圆弧之外
                                        '1 或开 将标注文字绘制在尺寸界线之间，即使 AutoCAD 通常将这些文字放置于尺寸界线之外。
        .SetVariable "DimTMOVE", 2      '设置标注文字的移动规则
                                        '0  尺寸线和标注文字一起移动
                                        '1  在移动标注文字时添加一条引线
                                        '2  允许标注文字自由移动而不用添加引线
        .SetVariable "DimTOFL", 0      '控制是否将尺寸线绘制在尺寸界线之间（即使文字放置在尺寸界线之外）
        .SetVariable "DimTOH", 0       '控制标注文字在尺寸界线外的位置
        .SetVariable "DimTSz", 0      '指定线性标注、半径标注以及直径标注中替代箭头的小斜线尺寸
        .SetVariable "DimTVP", 1        '控制尺寸线上方或下方标注文字的垂直位置
        .SetVariable "DimTxSty", "STANDARD"     '指定标注的文字样式
        .SetVariable "DimTxt", 50         '指定标注文字的高度，除非当前文字样式具有固定的高度
        .SetVariable "DimUPT", 0        '控制用户定位文字的选项
        .SetVariable "DimZIn", 0        '控制是否对主单位值作消零处理
'
       '定义换算单位的特性
        .SetVariable "DimAlt", 0        '控制标注中换算单位的显示
        .SetVariable "DimAltD", 4       '控制换算单位中小数位的位数
        .SetVariable "DimAltF", 25.4    '控制换算单位乘数
        .SetVariable "DimAltRnd", 0     '舍入换算标注单位
        .SetVariable "DimAltTD", 4      '设置标注换算单位公差值小数位的位数
        .SetVariable "DimAltTZ", 0      '控制是否对公差值作消零处理
        .SetVariable "DimAltU", 2       '为所有标注样式族（角度标注除外）换算单位设置单位格式
        .SetVariable "DimAltZ", 0       '控制是否对换算单位标注值作消零处理
        .SetVariable "DimAPost", ""     '为所有标注类型（角度标注除外）的换算标注测量值指定文字前缀或后缀（或两者都指定）
   End With
    '标注样式的特性从图形已有样式中获得
    
     dimStyle.CopyFrom ThisDrawing
     
    
    
    
End Sub

'文件自述：还差一部分内容

Attribute VB_Name = "模块1"
Sub aaa()
UserForm1.Show
End Sub
